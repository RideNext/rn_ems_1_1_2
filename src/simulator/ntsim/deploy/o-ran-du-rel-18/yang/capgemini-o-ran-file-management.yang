module capgemini-o-ran-file-management {
  yang-version 1.1;  
  namespace "urn:capgemini:o-ran-file-mgmt";
  prefix "capgemini-o-ran-file";

  import ietf-yang-types { prefix "yang"; }

  organization "www.capgemini.com";
  contact "www.capgemini.com";    

  description 
	"o ran file management extension";
  
  reference "TS 28532";
  revision 2022-01-20 { 
    description "Initial revision";
	reference "3GPP TS 28.532";
  }

  typedef FileType {
		type enumeration {
			enum PERFORMANCE {
				value 0;
				description "For performance data (including measurement data and KPI) files, the value is assigned to PERFORMANCE.";
			}
			enum TRACE { 
				value 1;
				description "For trace data files, the value is assigned to TRACE.";
			}
			enum ANALYTICS {
				value 2;
				description "For analytic data files, the value is assigned to ANALYTICS.";
			}
			enum PROPRIETARY {
				value 3;
				description "For proprietary data files, the value is assigned to PROPRIETARY.";
			}
		}
		description "It identifies the type of the management data stored in the file. Following are the allowed values:
					 - For performance data (including measurement data and KPI) files, the value is assigned to PERFORMANCE.
					 -  For trace data files, the value is assigned to TRACE.
					 -  For analytic data files, the value is assigned to ANALYTICS.
					 -  For proprietary data files, the value is assigned to PROPRIETARY.";
  }

  grouping fileInfoGrp{
  
    leaf fileLocation {
	  type string;
	  mandatory "true";
	  description "It identifies the location of the file. The location may be a directory path or a URL.";
	}

	leaf fileSize {
	  type int64;
	  description "It identifies the size of the file. 
		Its value is positive Integer (the unit is byte).";
	}

	leaf fileReadyTime {
	  type string;
	  description "It identifies the date and time when the file was last closed and made available in the management service producer and the file content will not be changed.";
	}
	
	leaf fileExpirationTime {
	  type string;
	  description "It identifies the date and time beyond which the file may be deleted.
		It shall not be empty and shall be later than fileReadyTime.";
	}
	
	leaf fileCompression {
	  type string;
	  mandatory "true";
	  description "It identifies the name of the compression algorithm used for the file. 
					An empty fileCompression means that there is no compression on the file. 
					Choice of compression algorithm is vendor-specific but is encouraged to use industrial standard algorithm such as GZIP.";
	}
	
	leaf fileFormat {
	  type string;
	  mandatory "true";
	  description "Identifier of the XML or ASN.1 schema (incl. its version) used to produce the file content";
	}
	
	leaf fileDataType {
        type FileType;
		mandatory "true";
        description "It identifies the type of the management data stored in the file.";      
    }
  }
  
  // Notifications
  notification notifyFileReady{
	  
	leaf objectClass {
	  type string;
	  mandatory true;
	  description "Class of the managed object, where the notifyFileReady occurred.";
	}
	leaf objectInstance {
	  type string;
	  mandatory true;
	  description "Instance of the managed object, where the notifyFileReady occurred.";
	}
	leaf notificationId {
	  type string;
	  mandatory true;
	  description "The identifier of the notification shall be chosen to be unique across all notifications of a particular managed object instance throughout the time that correlation is significant, 
	  it uniquely identifies the notification from other notifications generated by the subject MOI.";
	}
	leaf notificationType {
	  type string;
	  mandatory true;
	  description "notifyFileReady";
	}
	leaf eventTime {
	  type string;
	  mandatory true;
	  description "Time when the file, that triggered this notification, was ready for upload.";
	}  
	leaf systemDN {
	  type string;
	  mandatory true;
	  description "DN of the MnS Agent emitting the notification";
	}  
	container fileInfoList {
      uses fileInfoGrp;
      description "Information about the new file, 
	  that became ready for upload and triggered this notification.";
    }
	description "A MnS producer sends this notification to subscribed MnS consumers when a new file is ready (available) on the MnS producer for upload by a MnS consumer. 
	The fileInfoList parameter provides information (meta data) about the new file and optionally, 
	in addition to that, information about all other files, which became ready for upload earlier and are still available for upload when the notification is sent.";
  }
  
  notification notifyFilePreparationError {
	  
	leaf objectClass {
	  type string;
	  mandatory true;
	  description "Class of the managed object, where the notifyFilePreparationError occurred.";
	}
	leaf objectInstance {
	  type string;
	  mandatory true;
	  description "Instance of the managed object, where the notifyFilePreparationError occurred.";
	}
	leaf notificationId {
	  type string;
	  mandatory true;
	  description "The identifier of the notification shall be chosen to be unique across all notifications of a particular managed object instance throughout the time that correlation is significant, 
	  it uniquely identifies the notification from other notifications generated by the subject MOI.";
	}
	leaf notificationType {
	  type string;
	  mandatory true;
	  description "notifyFilePreparationError";
	}
	leaf eventTime {
	  type yang:date-and-time ;
	  mandatory true;
	  description "Time when the file preparation error occured.";
	}  
	leaf systemDN {
	  type string;
	  mandatory true;
	  description "DN of the MnS Agent emitting the notification";
	}  
	
	container fileInfoList {
      uses fileInfoGrp;    
      description "Each list item contains information about a file where a file preparation error occurred and that is kept on the MnS producer. Files, that are deleting or not created at all, have no list item..";
    }
	
	leaf reason {

	  type enumeration { 
        enum ERRORINPREPARATION {
            description "errorInPreparation.";
        }
        enum HARDDISKFULL {
            description "hardDiskFull.";
        }
		enum HARDDISKFAILURE {
            description "hardDiskFailure.";
        }
		enum TOOMANYFILES {
            description "tooManyFiles.";
        }
		enum COLLECTIONTIMEOUT {
            description "collectionTimeOut.";
        }
		enum INCOMPLETETRUNCATEDFILE {
            description "incompleteTruncatedFile.";
        }
		enum CORRUPTEDFILE {
            description "corruptedFile.";
        }
		enum LOWMEMORY {
            description "lowMemory.";
        }
		enum DATANOTAVAILABLE {
            description "dataNotAvailable.";
        }
      }
	  description "Detailed error reason, including
					- errorInPreparation
					- hardDiskFull
					- hardDiskFailure
					- tooManyFiles
					- collectionTimeOut
					- incompleteTruncatedFile
					- corruptedFile
					- lowMemory
					- dataNotAvailable
					";
	}
	description "A MnS producer sends this notification to subscribed MnS consumers when an error occurs while preparing a file. 
	For many error reasons, such as low memory or hard disk full, it is very likely that all ongoing file preparation process fail at the same time. 
	For that reason, it is possible to report with this notification that multiple file preparation processes failed.
	In case the MnS producer keeps the file, where an error occurred during preparation, 
	the fileInfoList parameter contains a list item with information about that file, otherwise, 
	if the file is deleted or not created at all, the fileInfoList parameter has no list item related to that file.";
  }
}
